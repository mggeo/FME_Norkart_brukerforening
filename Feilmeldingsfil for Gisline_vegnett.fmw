FME workspace Feilmeldingsfil for Gisline_vegnett.fmw

Parameters:
- DestDataset_TEXTLINE = E:\GEODATA   # Destination Text File
- SourceDataset_GDMMAPPERSOSI = E:\GEODATA\0516\FKB\3436_vegnett.sos   # Source GDM File
- FEATURE_TYPES_2 =
- SourceDataset_GDMMAPPERSOSI_3 = E:\GEODATA\0516\FKB\3436_vegnett.sos   # Source GDM File
- KommNR = 3436   # Angi kommunenummer

Readers:
- GDMMAPPERSOSI_1: GDMMAPPERSOSI from $(SourceDataset_GDMMAPPERSOSI)
- GDMMAPPERSOSI_2: GDMMAPPERSOSI from $(SourceDataset_GDMMAPPERSOSI_3)

Writers:
- TEXTLINE_1: TEXTLINE to $(DestDataset_TEXTLINE)

VegSenterlinje (reader GDMMAPPERSOSI_1) [off]
    attributes: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
Tester_3
    BOOL_OP = OR
    COMPOSITE_TEST = 1 OR 2
    TEST_CLAUSE:
      TEST GATENAVN ATTRIBUTE_HAS_A_VALUE ""
      TEST GATENR ATTRIBUTE_HAS_A_VALUE ""
    TEST_MODE = TEST
    FAILED -> Tester_2
Tester_2
    BOOL_OP = OR
    COMPOSITE_TEST = 1
    TEST_CLAUSE = TEST @Value(VNR.VEGKATEGORI) = P
    TEST_MODE = TEST
    PASSED -> CenterPointReplacer
    PASSED -> Tester_2_Failed
    FAILED -> CenterPointReplacer
    FAILED -> Tester_2_Failed
Tester_2_Failed: Inspector
Note: Kan gi misvisande punkt dersom svingete veg
CenterPointReplacer
    POINTTYPE = CENTEROFGRAV
    POINT -> CenterPointReplacer_Point
    POINT -> CoordinateExtractor

Bookmark: 3436
Kjørebane (reader GDMMAPPERSOSI_2)
    attributes: DATAFANGSTDATO number(9,0), OBJTYPE char(10), VLENKEID number(10,0), VNR.VEGKATEGORI char(2), VPA.HOVEDPARSELL number(4,0), VNR.VEGSTATUS char(2), VNR.VEGNUMMER number(6,0), KVALITET.MÅLEMETODE number(3,0), KVALITET.NØYAKTIGHET number(4,0), VPA.METER-FRA number(6,0), VPA.METER-TIL number(6,0), VFRADATO number(9,0), VKJORFLT char(6), FARTSGRENSE{}.FARTSGRENSE.FARTSGRENSEVERDI char(6), FUNKSJONELLVEGKLASSE.VEGKLASSE number(2,0), GATENAVN char(18), GATENR number(5,0), KVALITET.H-MÅLEMETODE number(3,0), KVALITET.H-NØYAKTIGHET number(2,0), KVALITET.SYNBARHET number(2,0), MEDIUM char(2)
    -> Tester_3
Kjørefelt (reader GDMMAPPERSOSI_2)
    attributes: DATAFANGSTDATO number(9,0), GATENR number(5,0), OBJTYPE char(10), VNR.VEGSTATUS char(2), GATENAVN char(19), VNR.VEGKATEGORI char(2), VNR.VEGNUMMER number(5,0), KVALITET.MÅLEMETODE number(3,0), KVALITET.NØYAKTIGHET number(4,0), VLENKEID number(10,0), VPA.HOVEDPARSELL number(3,0), VPA.METER-FRA number(5,0), VPA.METER-TIL number(5,0), VFRADATO number(9,0), FARTSGRENSE{}.FARTSGRENSE.FARTSGRENSEVERDI number(9,0), FUNKSJONELLVEGKLASSE.VEGKLASSE number(2,0), MEDIUM char(2), VKJORFLT char(4)
    -> Tester_3
VegSenterlinje (reader GDMMAPPERSOSI_2)
    attributes: GATENR number(5,0), OBJTYPE char(15), VNR.VEGSTATUS char(2), GATENAVN char(20), VNR.VEGKATEGORI char(2), VNR.VEGNUMMER number(6,0), KVALITET.MÅLEMETODE number(3,0), KVALITET.SYNBARHET number(2,0), KVALITET.NØYAKTIGHET number(4,0), KVALITET.H-MÅLEMETODE number(3,0), KVALITET.H-NØYAKTIGHET number(4,0), DATAFANGSTDATO number(9,0), VLENKEID number(10,0), ENDRINGSFLAGG.ENDRET_TYPE char(2), VPA.HOVEDPARSELL number(4,0), VPA.METER-FRA number(6,0), VPA.METER-TIL number(6,0), VFRADATO number(9,0), VKJORFLT char(8), FARTSGRENSE{}.FARTSGRENSE.FARTSGRENSEVERDI char(8), FUNKSJONELLVEGKLASSE.VEGKLASSE number(2,0), ENDRINGSFLAGG.ENDRET_TID number(9,0), LBVKLASSE number(2,0), MEDIUM char(2), SIDEVEG char(4), VTILDATO number(9,0)
    -> Tester_3

Bookmark: Genererer feilmeldingsfil
CoordinateExtractor
    IND = 0
    MODE = Specify Coordinate
    X_ATTR = _x
    Y_ATTR = _y
    Z_ATTR = _z
    -> AttributeCreator_3
Note: Lagar meldingstekst til tekstfil
AttributeCreator_3
    ATTR_TABLE = SET_TO MELD = MELD: @Value(_y) @Value(_x) @Value(OBJTYPE) @Value(VLENKEID)
    -> Sorter
    -> FIL
FIL: Inspector
    TACKATTRS = VNR.VEGKATEGORI
Sorter
    SORT_PARM = VLENKEID NUMERIC ASCENDING
    SORTED -> text_line (writer TEXTLINE_1)
text_line (writer TEXTLINE_1)
    attributes: text_line_data buffer
CenterPointReplacer_Point: Inspector
